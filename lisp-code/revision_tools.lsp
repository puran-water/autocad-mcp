;;; Native DWG revision primitives. AutoCAD LT AutoLISP; no external COM.
(vl-load-com)
(setq pcad:version "1.0")
;;; Layer table renames preserve entity handles and all display/plot properties.
(defun pcad:layer-properties (name / d)
  (setq d (entget (tblobjname "LAYER" name)))
  (vl-remove-if '(lambda (p) (member (car p) '(-1 2))) d))
(defun pcad:rename-layers-work (expected pairs path / pair before after entries layer)
  (pcad:assert-doc expected)
  (pcad:require (and (> (length pairs) 0) (<= (length pairs) 7)) "LAYER_BATCH_1_TO_7_REQUIRED")
  (pcad:require (not (findfile path)) "JOURNAL_EXISTS_RECONCILE_FIRST")
  (foreach pair pairs
    (pcad:require (not (member (strcase (car pair)) '("0" "DEFPOINTS"))) "RESERVED_LAYER")
    (pcad:require (tblsearch "LAYER" (car pair)) "SOURCE_LAYER_MISSING")
    (pcad:require (and (snvalid (cadr pair)) (not (tblsearch "LAYER" (cadr pair)))) "TARGET_LAYER_EXISTS_OR_INVALID"))
  (setq entries nil)
  (pcad:journal path "layer-renames" "native-properties" "prepared" entries)
  (foreach pair pairs
    (setq before (pcad:layer-properties (car pair)))
    (pcad:journal path "layer-renames" "native-properties" "running" entries)
    (setq layer (vla-Item (vla-get-Layers (vla-get-ActiveDocument (vlax-get-acad-object))) (car pair)))
    (vla-put-Name layer (cadr pair))
    (setq after (pcad:layer-properties (cadr pair)))
    (pcad:require (and (not (tblsearch "LAYER" (car pair))) (equal before after)) "LAYER_PROPERTIES_CHANGED")
    (setq entries (append entries (list (pcad:obj (list (cons "old" (car pair)) (cons "new" (cadr pair))
      (cons "properties" (pcad:arr (mapcar '(lambda (p) (list (car p) (cdr p))) after))))))))
    (pcad:journal path "layer-renames" "native-properties" "running" entries))
  (pcad:journal path "layer-renames" "native-properties" "complete" entries)
  (pcad:json (pcad:obj (list (cons "state" "complete") (cons "journal" path) (cons "entries" (pcad:arr entries))))))
(defun pcad:rename-layers (expected pairs path / doc result)
  (pcad:assert-doc expected)
  (setq doc (vla-get-ActiveDocument (vlax-get-acad-object)))
  (vla-StartUndoMark doc)
  (setq result (vl-catch-all-apply 'pcad:rename-layers-work (list expected pairs path)))
  (vla-EndUndoMark doc)
  (if (vl-catch-all-error-p result) (pcad:fail (pcad:message result)) result))
(defun pcad:fail (message) (setq pcad:last-error message) (exit))
(defun pcad:message (result) (if pcad:last-error pcad:last-error (vl-catch-all-error-message result)))
(defun pcad:run (fn args / result)
  (setq pcad:last-error nil pcad:created nil)
  (setq result (vl-catch-all-apply fn args))
  (if (vl-catch-all-error-p result)
    (pcad:json (pcad:obj (list (cons "ok" 'pcad-false) (cons "created_handles" (pcad:arr pcad:created)) (cons "error" (pcad:message result)))))
    (if (= (type result) 'STR) result (pcad:json result))))
(defun pcad:obj (pairs) (list 'pcad-object pairs))
(defun pcad:arr (items) (list 'pcad-array items))
(defun pcad:quote (s) (strcat "\"" (mcp-escape-string s) "\""))
(defun pcad:join (xs sep / out) (setq out "") (foreach x xs (setq out (strcat out (if (= out "") "" sep) x))) out)
(defun pcad:json (v / s)
  (cond
    ((null v) "null") ((eq v T) "true")
    ((eq v 'pcad-false) "false") ((eq v :vlax-true) "true") ((eq v :vlax-false) "false")
    ((= (type v) 'STR) (pcad:quote v))
    ((= (type v) 'INT) (itoa v))
    ((= (type v) 'REAL) (setq s (rtos v 2 12))
      (cond ((= (substr s 1 1) ".") (strcat "0" s))
            ((= (substr s 1 2) "-.") (strcat "-0" (substr s 2))) (T s)))
    ((= (type v) 'ENAME) (pcad:quote (cdr (assoc 5 (entget v)))))
    ((and (listp v) (eq (car v) 'pcad-object))
      (strcat "{" (pcad:join (mapcar '(lambda (p) (strcat (pcad:quote (car p)) ":" (pcad:json (cdr p)))) (cadr v)) ",") "}"))
    ((and (listp v) (eq (car v) 'pcad-array))
      (strcat "[" (pcad:join (mapcar 'pcad:json (cadr v)) ",") "]"))
    ((listp v) (pcad:json (pcad:arr v)))
    (T (pcad:quote (vl-princ-to-string v)))))
(defun pcad:write-json (path value / f tmp prev)
  (setq tmp (strcat path ".tmp") prev (strcat path ".previous"))
  (if (not (setq f (open tmp "w" "utf8"))) (pcad:fail "OUTPUT_OPEN_FAILED"))
  (write-line (pcad:json value) f) (close f)
  (if (findfile prev) (vl-file-delete prev))
  (if (findfile path) (pcad:require (vl-file-rename path prev) "JOURNAL_BACKUP_FAILED"))
  (pcad:require (vl-file-rename tmp path) "JOURNAL_RENAME_FAILED") path)
(defun pcad:fullpath () (strcat (getvar "DWGPREFIX") (getvar "DWGNAME")))
(defun pcad:path-equal (a b) (= (strcase (vl-string-translate "\\" "/" a)) (strcase (vl-string-translate "\\" "/" b))))
(defun pcad:assert-doc (expected)
  (if (not (pcad:path-equal expected (pcad:fullpath))) (pcad:fail "WRONG_DOCUMENT")))
(defun pcad:prop (o name / r)
  (setq r (vl-catch-all-apply 'vlax-get-property (list o name)))
  (if (vl-catch-all-error-p r) nil r))
(defun pcad:box (e / a b r)
  (setq r (vl-catch-all-apply 'vla-GetBoundingBox (list (vlax-ename->vla-object e) 'a 'b)))
  (if (vl-catch-all-error-p r) nil (list (vlax-safearray->list a) (vlax-safearray->list b))))
(defun pcad:dxf (e / d)
  (setq d (entget e))
  (mapcar '(lambda (p) (list (car p) (cdr p))) (vl-remove-if '(lambda (p) (= (car p) -1)) d)))
(defun pcad:attrs (e / d n out)
  (setq d (entget e) out nil)
  (if (and (= (cdr (assoc 0 d)) "INSERT") (= (cdr (assoc 66 d)) 1))
    (progn (setq n (entnext e))
      (while (and n (/= (cdr (assoc 0 (entget n))) "SEQEND"))
        (if (= (cdr (assoc 0 (entget n))) "ATTRIB") (setq out (cons (pcad:entity n) out)))
        (setq n (entnext n)))))
  (reverse out))
(defun pcad:text (d / result)
  (setq result "")
  (if (member (cdr (assoc 0 d)) '("TEXT" "MTEXT" "ATTRIB" "ATTDEF"))
    (foreach p d (if (member (car p) '(1 3)) (setq result (strcat result (cdr p)))))) result)
(defun pcad:entity (e / d typ)
  (setq d (entget e) typ (cdr (assoc 0 d)))
  (pcad:obj (list (cons "handle" (cdr (assoc 5 d))) (cons "type" typ)
    (cons "layer" (cdr (assoc 8 d))) (cons "space" (cdr (assoc 410 d)))
    (cons "owner" (cdr (assoc 330 d))) (cons "bbox" (pcad:box e))
    (cons "text" (pcad:text d)) (cons "name" (cdr (assoc 2 d)))
    (cons "position" (cdr (assoc 10 d))) (cons "end" (cdr (assoc 11 d)))
    (cons "scale" (if (= typ "INSERT") (list (cdr (assoc 41 d)) (cdr (assoc 42 d)) (cdr (assoc 43 d)))))
    (cons "rotation" (cdr (assoc 50 d)))
    (cons "attributes" (pcad:arr (if (= typ "INSERT") (pcad:attrs e))))
    (cons "dxf" (pcad:arr (pcad:dxf e))))))
(defun pcad:layouts (/ doc out lo w h org)
  (setq doc (vla-get-ActiveDocument (vlax-get-acad-object)) out nil)
  (vlax-for lo (vla-get-Layouts doc)
    (vla-GetPaperSize lo 'w 'h)
    (setq out (cons (pcad:obj (list
      (cons "name" (vla-get-Name lo)) (cons "order" (vla-get-TabOrder lo))
      (cons "device" (vla-get-ConfigName lo)) (cons "media" (vla-get-CanonicalMediaName lo))
      (cons "style" (vla-get-StyleSheet lo)) (cons "plot_type" (vla-get-PlotType lo))
      (cons "paper_mm" (list w h)) (cons "rotation" (vla-get-PlotRotation lo))
      (cons "paper_units" (vla-get-PaperUnits lo))
      (cons "scale" (vla-get-StandardScale lo)) (cons "plot_with_styles" (vla-get-PlotWithPlotStyles lo)))) out)))
  (reverse out))
(defun pcad:inventory (/ doc styles blocks origins out s b)
  (setq doc (vla-get-ActiveDocument (vlax-get-acad-object)) styles nil blocks nil origins nil)
  (vlax-for s (vla-get-TextStyles doc)
    (setq styles (cons (pcad:obj (list (cons "name" (vla-get-Name s))
      (cons "font" (vla-get-FontFile s)) (cons "resolved" (findfile (vla-get-FontFile s)))
      (cons "bigfont" (vla-get-BigFontFile s)))) styles)))
  (vlax-for b (vla-get-Blocks doc)
    (setq origins (cons (pcad:obj (list (cons "name" (vla-get-Name b))
      (cons "origin" (vlax-safearray->list (vlax-variant-value (vla-get-Origin b)))))) origins))
    (if (= (vla-get-IsXRef b) :vlax-true)
      (setq blocks (cons (pcad:obj (list (cons "name" (vla-get-Name b))
        (cons "path" (pcad:prop b 'Path)))) blocks))))
  (pcad:obj (list (cons "version" pcad:version) (cons "drawing" (pcad:fullpath))
    (cons "layouts" (pcad:arr (pcad:layouts))) (cons "styles" (pcad:arr (reverse styles)))
    (cons "block_origins" (pcad:arr (reverse origins))) (cons "xrefs" (pcad:arr (reverse blocks))))))
(defun pcad:export (expected path / f ss i count blocks b e)
  (pcad:assert-doc expected)
  (if (not (setq f (open path "w" "utf8"))) (pcad:fail "OUTPUT_OPEN_FAILED"))
  (write-line (pcad:json (pcad:obj (list (cons "record" "header") (cons "data" (pcad:inventory))))) f)
  (setq ss (ssget "_X") i 0 count 0)
  (if ss (repeat (sslength ss)
    (setq e (ssname ss i))
    (write-line (pcad:json (pcad:obj (list (cons "record" "entity") (cons "data" (pcad:entity e))))) f)
    (setq i (1+ i) count (1+ count))))
  (vlax-for b (vla-get-Blocks (vla-get-ActiveDocument (vlax-get-acad-object)))
    (if (and (= (vla-get-IsLayout b) :vlax-false) (= (vla-get-IsXRef b) :vlax-false))
      (vlax-for ob b
        (setq e (vlax-vla-object->ename ob))
        (write-line (pcad:json (pcad:obj (list (cons "record" "block_entity")
          (cons "block" (vla-get-Name b)) (cons "data" (pcad:entity e))))) f))))
  (write-line (pcad:json (pcad:obj (list (cons "record" "complete") (cons "entities" count)))) f)
  (close f)
  (pcad:json (pcad:obj (list (cons "path" path) (cons "entities" count) (cons "drawing" (pcad:fullpath))))))
(defun pcad:read-handles (expected handles)
  (pcad:assert-doc expected)
  (pcad:json (pcad:arr (mapcar '(lambda (h) (if (handent h) (pcad:entity (handent h))
    (pcad:obj (list (cons "handle" h) (cons "missing" T))))) handles))))
(princ)

;;; Operations are data, not strings of commands. Seven edits at most per batch.
(defun pcad:g (k xs) (cdr (assoc k xs)))
(defun pcad:require (test message) (if (not test) (pcad:fail message)))
(defun pcad:checked (op / e d actual)
  (setq e (handent (pcad:g "handle" op)))
  (pcad:require e "HANDLE_MISSING") (setq d (entget e))
  (pcad:require (pcad:g "expect" op) "EXPECTED_STATE_REQUIRED")
  (foreach p (pcad:g "expect" op)
    (setq actual (cdr (assoc (car p) d)))
    (if (= (type actual) 'ENAME) (setq actual (cdr (assoc 5 (entget actual)))))
    (pcad:require (equal actual (cdr p) 0.00000001)
      (strcat "OLD_VALUE_MISMATCH handle=" (pcad:g "handle" op) " dxf=" (itoa (car p))
        " expected=" (vl-prin1-to-string (cdr p)) " actual=" (vl-prin1-to-string actual))))
  (pcad:require (= 0 (logand 4 (cdr (assoc 70 (tblsearch "LAYER" (cdr (assoc 8 d))))))) "LAYER_LOCKED") e)
(defun pcad:attribute-targets (e op / o at out p matches target)
  (pcad:require (= (cdr (assoc 0 (entget e))) "INSERT") "INSERT_REQUIRED")
  (pcad:require (and (pcad:g "attributes" op) (<= (length (pcad:g "attributes" op)) 16)) "ATTRIBUTE_MAP_1_TO_16_REQUIRED")
  (setq o (vlax-ename->vla-object e))
  (pcad:require (= (vla-get-HasAttributes o) :vlax-true) "INSERT_HAS_NO_ATTRIBUTES")
  (setq at (vlax-invoke o 'GetAttributes) out nil)
  (foreach p (pcad:g "attributes" op)
    (setq matches (vl-remove-if-not '(lambda (a) (= (strcase (vla-get-TagString a)) (strcase (car p)))) at))
    (pcad:require (= (length matches) 1) "ATTRIBUTE_TAG_NOT_UNIQUE")
    (setq target (car matches))
    (pcad:require (assoc (car p) (pcad:g "expected_attributes" op)) "EXPECTED_ATTRIBUTE_REQUIRED")
    (pcad:require (= (vla-get-TextString target) (cdr (assoc (car p) (pcad:g "expected_attributes" op)))) "OLD_ATTRIBUTE_MISMATCH")
    (pcad:require (= 0 (logand 4 (cdr (assoc 70 (tblsearch "LAYER" (vla-get-Layer target)))))) "LAYER_LOCKED")
    (setq out (cons (cons target (cdr p)) out)))
  (reverse out))
(defun pcad:preflight (op / kind e d fields tags n tag c a b p)
  (setq kind (pcad:g "kind" op))
  (pcad:require (pcad:g "item" op) "ITEM_REQUIRED")
  (pcad:require (member kind '("spline-gap" "attributes" "patch" "text" "scale" "rotate" "move" "erase" "copy" "line" "insert" "cloud" "polyline" "mtext" "vertices" "split-line")) "OPERATION_UNSUPPORTED")
  (if (member kind '("spline-gap" "attributes" "patch" "text" "scale" "rotate" "move" "erase" "copy" "vertices" "split-line"))
    (progn (setq e (pcad:checked op) d (entget e))
      (if (= kind "spline-gap") (progn
        (pcad:require (= (cdr (assoc 0 d)) "SPLINE") "SPLINE_REQUIRED")
        (pcad:require (= (getvar "CMDACTIVE") 0) "COMMAND_ACTIVE")
        (pcad:require (not (vlax-curve-isClosed e)) "OPEN_CURVE_REQUIRED")
        (pcad:require (equal (vl-remove-if '(lambda (p) (member (car p) '(-1 330))) d)
          (mapcar '(lambda (p) (cons (car p) (cadr p)))
            (vl-remove-if '(lambda (p) (member (car p) '(-1 330))) (pcad:g "expected_dxf" op)))
          0.00000001) "OLD_CURVE_MISMATCH")
        (setq a (car (pcad:g "gap" op)) b (cadr (pcad:g "gap" op)))
        (foreach p (list a b)
          (pcad:require (< (distance p (vlax-curve-getClosestPointTo e p)) 0.000001) "GAP_POINT_OFF_CURVE"))
        (pcad:require (and (< (vlax-curve-getStartParam e) (vlax-curve-getParamAtPoint e a))
          (< (vlax-curve-getParamAtPoint e a) (vlax-curve-getParamAtPoint e b))
          (< (vlax-curve-getParamAtPoint e b) (vlax-curve-getEndParam e))) "ORDERED_INTERIOR_GAP_REQUIRED")))
      (if (= kind "attributes") (pcad:attribute-targets e op))
      (if (= kind "rotate") (progn
        (pcad:require (= (cdr (assoc 0 d)) "INSERT") "INSERT_REQUIRED")
        (foreach c '(10 50 210)
          (pcad:require (assoc c (pcad:g "expect" op)) "EXPECTED_ROTATION_ANCHOR_NORMAL_REQUIRED"))
        (pcad:require (equal (cdr (assoc 210 d)) '(0.0 0.0 1.0) 0.00000001) "PLANAR_INSERT_REQUIRED")
        (pcad:require (and (numberp (pcad:g "target" op)) (>= (pcad:g "target" op) 0.0)
          (< (pcad:g "target" op) (* 2 pi))) "ROTATION_RADIANS_0_TO_2PI_REQUIRED")
        (if (= (vla-get-HasAttributes (vlax-ename->vla-object e)) :vlax-true)
          (foreach a (vlax-invoke (vlax-ename->vla-object e) 'GetAttributes)
            (pcad:require (= 0 (logand 4 (cdr (assoc 70 (tblsearch "LAYER" (vla-get-Layer a)))))) "LAYER_LOCKED")))))
      (if (= kind "text") (progn
        (pcad:require (member (cdr (assoc 0 d)) '("TEXT" "MTEXT" "ATTRIB")) "TEXT_ENTITY_REQUIRED")
        (pcad:require (= (pcad:text d) (pcad:g "expected_text" op)) "OLD_TEXT_MISMATCH")))
      (if (= kind "patch")
        (foreach p (pcad:g "set" op)
          (pcad:require (not (and (= (car p) 1) (= (cdr (assoc 0 d)) "MTEXT"))) "USE_TEXT_OPERATION_FOR_MTEXT")
          (pcad:require (member (car p) '(1 2 6 7 8 10 11 40 41 42 43 48 50 62 370)) "DXF_FIELD_NOT_EDITABLE")
          (if (= (car p) 6) (progn
            (pcad:require (and (= (type (cdr p)) 'STR) (/= (vl-string-trim " \t\r\n" (cdr p)) "")) "INVALID_DXF_LINETYPE")
            (pcad:require (or (member (strcase (cdr p)) '("BYLAYER" "BYBLOCK"))
              (tblsearch "LTYPE" (cdr p))) "LINETYPE_NOT_LOADED")))
          (if (= (car p) 48)
            (pcad:require (and (numberp (cdr p)) (> (cdr p) 0.0)) "INVALID_DXF_LINETYPE_SCALE"))
          (if (= (car p) 370)
            (pcad:require (and (= (type (cdr p)) 'INT)
              (member (cdr p) '(-3 -2 -1 0 5 9 13 15 18 20 25 30 35 40 50 53 60 70 80 90 100 106 120 140 158 200 211))) "INVALID_DXF_LINEWEIGHT"))
          (pcad:require (assoc (car p) (pcad:g "expect" op)) "EXPECTED_FIELD_REQUIRED")))
      (if (= kind "scale") (progn
        (pcad:require (= (cdr (assoc 0 d)) "INSERT") "INSERT_REQUIRED")
        (foreach c '(41 42 43) (pcad:require (assoc c (pcad:g "expect" op)) "EXPECTED_SCALE_REQUIRED"))
        (pcad:require (> (pcad:g "target" op) 0.0) "POSITIVE_SCALE_REQUIRED")
        (pcad:require (and (equal (abs (cdr (assoc 41 d))) (abs (cdr (assoc 42 d))) 0.00000001)
          (equal (abs (cdr (assoc 41 d))) (abs (cdr (assoc 43 d))) 0.00000001)) "NONUNIFORM_SCALE_REQUIRES_EXPLICIT_EDIT")))
      (if (= kind "vertices") (progn
        (pcad:require (= (cdr (assoc 0 d)) "LWPOLYLINE") "LWPOLYLINE_REQUIRED")
        (pcad:require (equal (cdr (assoc 210 d)) '(0.0 0.0 1.0) 0.00000001) "PLANAR_POLYLINE_REQUIRED")
        (pcad:require (equal (mapcar 'cdr (vl-remove-if-not '(lambda (p) (= (car p) 10)) d)) (pcad:g "expected_points" op) 0.00000001) "OLD_VERTICES_MISMATCH")
        (foreach p d (if (= (car p) 42) (pcad:require (= (cdr p) 0.0) "CURVED_POLYLINE_REQUIRES_EXPLICIT_EDIT")))))
      (if (= kind "split-line") (progn
        (pcad:require (= (cdr (assoc 0 d)) "LINE") "LINE_REQUIRED")
        (foreach c '(10 11) (pcad:require (assoc c (pcad:g "expect" op)) "EXPECTED_ENDPOINT_REQUIRED"))))))
  (if (member kind '("line" "insert" "cloud" "polyline" "mtext"))
    (progn
      (pcad:require (pcad:g "space" op) "SPACE_REQUIRED")
      (pcad:require (tblsearch "LAYER" (pcad:g "layer" op)) "LAYER_MISSING")
      (pcad:require (= 0 (logand 4 (cdr (assoc 70 (tblsearch "LAYER" (pcad:g "layer" op)))))) "LAYER_LOCKED")))
  (if (= kind "insert") (progn
    (pcad:require (tblsearch "BLOCK" (pcad:g "name" op)) "BLOCK_MISSING")
    (setq tags nil n (tblobjname "BLOCK" (pcad:g "name" op)))
    (setq n (entnext n))
    (while (and n (/= (cdr (assoc 0 (entget n))) "ENDBLK"))
      (setq d (entget n))
      (if (and (= (cdr (assoc 0 d)) "ATTDEF") (= 0 (logand 2 (cdr (assoc 70 d)))))
        (setq tags (cons (strcase (cdr (assoc 2 d))) tags)))
      (setq n (entnext n)))
    (foreach p (pcad:g "attributes" op)
      (setq tag (strcase (car p)))
      (pcad:require (= 1 (length (vl-remove-if-not '(lambda (v) (= v tag)) tags))) "ATTRIBUTE_TAG_NOT_UNIQUE")))) T)
(defun pcad:space (name)
  (vla-get-Block (vla-Item (vla-get-Layouts (vla-get-ActiveDocument (vlax-get-acad-object))) name)))
(defun pcad:point (p) (vlax-3d-point (list (car p) (cadr p) (if (caddr p) (caddr p) 0.0))))
(defun pcad:handle (o / h) (setq h (vla-get-Handle o) pcad:created (cons h pcad:created)) h)
(defun pcad:new-line (space a b layer / o)
  (setq o (vla-AddLine (pcad:space space) (pcad:point a) (pcad:point b)))
  (pcad:handle o) (vla-put-Layer o layer) (vla-get-Handle o))
(defun pcad:poly (space points layer closed / coords ar o)
  (setq coords (apply 'append (mapcar '(lambda (p) (list (car p) (cadr p))) points)))
  (setq ar (vlax-make-safearray vlax-vbDouble (cons 0 (1- (length coords)))))
  (vlax-safearray-fill ar coords)
  (setq o (vla-AddLightWeightPolyline (pcad:space space) ar))
  (pcad:handle o) (vla-put-Layer o layer) (vla-put-Closed o (if closed :vlax-true :vlax-false)) o)
(defun pcad:cloud (op / lo hi step pts a b n i sides o tri text h x y out outline marker side)
  (setq lo (pcad:g "min" op) hi (pcad:g "max" op) step (pcad:g "arc" op)
    h (pcad:g "text_height" op) pts nil)
  (pcad:require (and (> step 0) (> h 0) (< (car lo) (car hi)) (< (cadr lo) (cadr hi))) "INVALID_CLOUD_BOUNDS")
  (setq outline (pcad:g "points" op))
  (if (not outline) (setq outline (list lo (list (car hi) (cadr lo)) hi (list (car lo) (cadr hi)))))
  (setq sides (mapcar 'list outline (append (cdr outline) (list (car outline)))))
  (foreach side sides
    (setq a (car side) b (cadr side) n (max 1 (fix (+ 0.999999 (/ (distance a b) step)))) i 0)
    (pcad:require (<= (+ (length pts) n) 4096) "CLOUD_TOO_COMPLEX")
    (repeat n (setq pts (cons (mapcar '(lambda (aa bb) (+ aa (* (/ (float i) n) (- bb aa)))) a b) pts) i (1+ i))))
  (setq pts (reverse pts) o (pcad:poly (pcad:g "space" op) pts (pcad:g "layer" op) T) i 0)
  (repeat (length pts) (vla-SetBulge o i 0.414213562373095) (setq i (1+ i)))
  (setq marker (pcad:g "marker_position" op))
  (setq x (if marker (car marker) (+ (car hi) (* 3 h))) y (if marker (cadr marker) (cadr hi)))
  (setq tri (pcad:poly (pcad:g "space" op)
    (list (list (- x (* 2 h)) (- y h)) (list (+ x (* 2 h)) (- y h)) (list x (+ y (* 2.5 h)))) (pcad:g "layer" op) T))
  (setq text (vla-AddText (pcad:space (pcad:g "space" op)) (pcad:g "revision" op) (pcad:point (list x y)) h))
  (pcad:handle text) (vla-put-Layer text (pcad:g "layer" op))
  (if (pcad:g "style" op) (vla-put-StyleName text (pcad:g "style" op)))
  (vla-put-Alignment text 10) (vla-put-TextAlignmentPoint text (pcad:point (list x y)))
  (list (vla-get-Handle o) (vla-get-Handle tri) (vla-get-Handle text)))
(defun pcad:apply (op / kind e d o result at old factor after p a b cuts l h prop)
  (setq kind (pcad:g "kind" op))
  (if (pcad:g "handle" op) (setq e (pcad:checked op) d (entget e) o (vlax-ename->vla-object e)))
  (cond
    ((= kind "spline-gap")
      (setq a (car (pcad:g "gap" op)) b (cadr (pcad:g "gap" op)) old (entlast))
      (command-s "_.BREAK" e "_F" "_non" (trans a 0 1) "_non" (trans b 0 1))
      (setq after (entlast))
      (pcad:require (and (entget e) (/= old after) (/= e after)
        (= (cdr (assoc 0 (entget after))) "SPLINE")) "SPLINE_SPLIT_READBACK_FAILED")
      (setq h (cdr (assoc 5 (entget after))) pcad:created (list h))
      (pcad:require (and (< (distance (vlax-curve-getEndPoint e) a) 0.000001)
        (< (distance (vlax-curve-getStartPoint after) b) 0.000001)) "GAP_ENDPOINT_READBACK_FAILED")
      (list (pcad:g "handle" op) h))
    ((= kind "attributes")
      (setq at (pcad:attribute-targets e op))
      (foreach p at
        (vla-put-TextString (car p) (cdr p)) (vla-Update (car p))
        (pcad:require (= (vla-get-TextString (car p)) (cdr p)) "ATTRIBUTE_READBACK_MISMATCH"))
      (vla-Update o) (list (pcad:g "handle" op)))
    ((= kind "text")
      (pcad:require (= (pcad:text d) (pcad:g "expected_text" op)) "OLD_TEXT_MISMATCH")
      (vla-put-TextString o (pcad:g "text" op)) (vla-Update o)
      (pcad:require (= (vla-get-TextString o) (pcad:g "text" op)) "TEXT_READBACK_MISMATCH")
      (list (pcad:g "handle" op)))
    ((= kind "patch")
      (foreach p (pcad:g "set" op)
        (if (assoc (car p) d) (setq d (subst p (assoc (car p) d) d)) (setq d (append d (list p)))))
      (pcad:require (entmod d) "ENTMOD_FAILED") (entupd e)
      (foreach p (pcad:g "set" op) (pcad:require (equal (cdr (assoc (car p) (entget e))) (cdr p) 0.00000001) "READBACK_MISMATCH"))
      (list (pcad:g "handle" op)))
    ((= kind "scale")
      (setq factor (/ (pcad:g "target" op) (abs (cdr (assoc 41 d)))))
      (vla-ScaleEntity o (pcad:point (cdr (assoc 10 d))) factor)
      (foreach c '(41 42 43) (pcad:require (equal (abs (cdr (assoc c (entget e)))) (pcad:g "target" op) 0.00000001) "SCALE_READBACK_MISMATCH"))
      (list (pcad:g "handle" op)))
    ((= kind "move") (vla-Move o (pcad:point '(0 0 0)) (pcad:point (pcad:g "delta" op))) (list (pcad:g "handle" op)))
    ((= kind "rotate")
      (vla-Rotate o (pcad:point (cdr (assoc 10 d))) (- (pcad:g "target" op) (cdr (assoc 50 d))))
      (vla-Update o)
      (pcad:require (equal (cdr (assoc 50 (entget e))) (pcad:g "target" op) 0.00000001) "ROTATION_READBACK_MISMATCH")
      (pcad:require (equal (cdr (assoc 10 (entget e))) (cdr (assoc 10 d)) 0.00000001) "ROTATION_ANCHOR_CHANGED")
      (list (pcad:g "handle" op)))
    ((= kind "erase") (entdel e) (pcad:require (null (entget e)) "ERASE_READBACK_MISMATCH") nil)
    ((= kind "copy") (setq o (vla-Copy o)) (pcad:handle o) (vla-Move o (pcad:point '(0 0 0)) (pcad:point (pcad:g "delta" op))) (list (pcad:handle o)))
    ((= kind "line") (list (pcad:new-line (pcad:g "space" op) (pcad:g "start" op) (pcad:g "end" op) (pcad:g "layer" op))))
    ((= kind "insert")
      (setq o (vla-InsertBlock (pcad:space (pcad:g "space" op)) (pcad:point (pcad:g "position" op))
        (pcad:g "name" op) (pcad:g "scale" op) (pcad:g "scale" op) (pcad:g "scale" op) (pcad:g "rotation" op)))
      (pcad:handle o) (vla-put-Layer o (pcad:g "layer" op))
      (if (pcad:g "attributes" op)
        (progn
          (pcad:require (= (vla-get-HasAttributes o) :vlax-true) "INSERT_HAS_NO_ATTRIBUTES")
          (setq at (vlax-invoke o 'GetAttributes))
          (foreach p (pcad:g "attributes" op)
            (setq result (vl-remove-if-not '(lambda (a) (= (strcase (vla-get-TagString a)) (strcase (car p)))) at))
            (pcad:require (= (length result) 1) "ATTRIBUTE_TAG_NOT_UNIQUE")
            (vla-put-TextString (car result) (cdr p))
            (pcad:require (= (vla-get-TextString (car result)) (cdr p)) "ATTRIBUTE_READBACK_MISMATCH"))))
      (list (pcad:handle o)))
    ((= kind "vertices")
      (setq at (apply 'append (pcad:g "points" op)) old (vlax-make-safearray vlax-vbDouble (cons 0 (1- (length at)))))
      (vlax-safearray-fill old at) (vla-put-Coordinates o old)
      (pcad:require (equal (vlax-safearray->list (vlax-variant-value (vla-get-Coordinates o))) at 0.00000001) "VERTICES_READBACK_MISMATCH")
      (list (pcad:g "handle" op)))
    ((= kind "mtext")
      (setq o (vla-AddMText (pcad:space (pcad:g "space" op)) (pcad:point (pcad:g "position" op)) (pcad:g "width" op) (pcad:g "text" op)))
      (pcad:handle o) (vla-put-Layer o (pcad:g "layer" op)) (vla-put-Height o (pcad:g "height" op))
      (if (pcad:g "style" op) (vla-put-StyleName o (pcad:g "style" op)))
      (list (vla-get-Handle o)))
    ((= kind "polyline")
      (setq o (pcad:poly (pcad:g "space" op) (pcad:g "points" op) (pcad:g "layer" op) (pcad:g "closed" op)))
      (list (vla-get-Handle o)))
    ((= kind "cloud") (pcad:cloud op))
    ((= kind "split-line")
      (setq a (cdr (assoc 10 d)) b (cdr (assoc 11 d)) cuts (pcad:g "gap" op) l (distance a b))
      (foreach p cuts (pcad:require (equal (+ (distance a p) (distance p b)) l 0.000001) "CUT_OFF_SEGMENT"))
      (pcad:require (< (distance a (car cuts)) (distance a (cadr cuts))) "CUT_ORDER_INVALID")
      (setq result (list (pcad:new-line (cdr (assoc 410 d)) a (car cuts) (cdr (assoc 8 d)))
                        (pcad:new-line (cdr (assoc 410 d)) (cadr cuts) b (cdr (assoc 8 d)))))
      (foreach h result
        (setq after (vlax-ename->vla-object (handent h)))
        (foreach prop '(Color Linetype LinetypeScale Lineweight)
          (vlax-put-property after prop (vlax-get-property o prop))))
      (entdel e) (pcad:require (null (entget e)) "ERASE_READBACK_MISMATCH") result)))
(defun pcad:journal (path id digest state entries)
  (pcad:write-json path (pcad:obj (list (cons "schema" "pcad.batch/v1") (cons "id" id)
    (cons "digest" digest) (cons "drawing" (pcad:fullpath)) (cons "state" state) (cons "entries" (pcad:arr entries))))))
(defun pcad:batch-work (expected id digest path ops / entries op before result state)
  (pcad:assert-doc expected)
  (pcad:require (and (> (length ops) 0) (<= (length ops) 7)) "BATCH_SIZE_1_TO_7_REQUIRED")
  (pcad:require (not (findfile path)) "BATCH_ALREADY_EXISTS_RECONCILE_JOURNAL")
  (foreach op ops (pcad:preflight op))
  (setq entries nil)
  (foreach op ops
    (setq before (if (pcad:g "handle" op) (pcad:entity (handent (pcad:g "handle" op)))))
    (setq entries (append entries (list (pcad:obj (list (cons "item" (pcad:g "item" op))
      (cons "kind" (pcad:g "kind" op)) (cons "state" "pending") (cons "before" before)))))))
  (pcad:journal path id digest "prepared" entries)
  (setq entries nil)
  (foreach op ops
    (setq before (if (pcad:g "handle" op) (pcad:entity (handent (pcad:g "handle" op)))))
    (pcad:journal path id digest "running" (append entries (list (pcad:obj (list (cons "item" (pcad:g "item" op)) (cons "state" "uncertain") (cons "before" before))))))
    (setq pcad:created nil)
    (setq result (vl-catch-all-apply 'pcad:apply (list op)))
    (if (vl-catch-all-error-p result)
      (progn
        (pcad:journal path id digest "interrupted" (append entries (list (pcad:obj (list
          (cons "item" (pcad:g "item" op)) (cons "state" "uncertain") (cons "before" before)
          (cons "created_handles" (pcad:arr pcad:created)) (cons "error" (pcad:message result)))))))
        (pcad:fail (pcad:message result)))
      (progn
        (pcad:require (or (= (pcad:g "kind" op) "erase") result) "MUTATION_RETURNED_NO_HANDLES")
        (setq entries (append entries (list (pcad:obj (list (cons "item" (pcad:g "item" op))
          (cons "kind" (pcad:g "kind" op)) (cons "state" "applied") (cons "before" before)
          (cons "handles" (pcad:arr result)) (cons "after" (pcad:arr (mapcar '(lambda (h) (pcad:entity (handent h))) result))))))))
        (pcad:journal path id digest "running" entries))))
  (pcad:journal path id digest "complete" entries)
  (pcad:json (pcad:obj (list (cons "journal" path) (cons "state" "complete") (cons "count" (length entries))))))
(defun pcad:batch (expected id digest path ops / doc vars result)
  (pcad:assert-doc expected)
  (setq doc (vla-get-ActiveDocument (vlax-get-acad-object))
    vars (mapcar '(lambda (n) (cons n (getvar n))) '("CMDECHO" "OSMODE" "ATTREQ" "ATTDIA")))
  (vla-StartUndoMark doc)
  (setvar "CMDECHO" 0) (setvar "OSMODE" 0) (setvar "ATTREQ" 0) (setvar "ATTDIA" 0)
  (setq result (vl-catch-all-apply 'pcad:batch-work (list expected id digest path ops)))
  (foreach p vars (setvar (car p) (cdr p)))
  (vla-EndUndoMark doc) (vla-Regen doc 1)
  (if (vl-catch-all-error-p result) (pcad:fail (pcad:message result)) result))
(defun pcad:plot-work (expected layout path / doc lo result)
  (pcad:assert-doc expected)
  (pcad:require (not (findfile path)) "PLOT_OUTPUT_EXISTS")
  (setq doc (vla-get-ActiveDocument (vlax-get-acad-object)) lo (vla-Item (vla-get-Layouts doc) layout))
  (pcad:require (/= (vla-get-ConfigName lo) "None") "PLOT_DEVICE_REQUIRED")
  (vla-put-ActiveLayout doc lo) (setvar "BACKGROUNDPLOT" 0)
  (setq result (vla-PlotToFile (vla-get-Plot doc) path))
  (pcad:require (= result :vlax-true) "PLOT_FAILED")
  (pcad:require (and (findfile path) (> (vl-file-size path) 0)) "PLOT_OUTPUT_MISSING")
  (pcad:json (pcad:obj (list (cons "path" path) (cons "layout" layout) (cons "bytes" (vl-file-size path))
    (cons "device" (vla-get-ConfigName lo)) (cons "media" (vla-get-CanonicalMediaName lo))
    (cons "style" (vla-get-StyleSheet lo))))))
(defun pcad:plot (expected layout path / bg tab result)
  (setq bg (getvar "BACKGROUNDPLOT") tab (getvar "CTAB"))
  (setq result (vl-catch-all-apply 'pcad:plot-work (list expected layout path)))
  (setvar "BACKGROUNDPLOT" bg) (setvar "CTAB" tab)
  (if (vl-catch-all-error-p result) (pcad:fail (pcad:message result)) result))
(defun pcad:save (expected path format / doc)
  (pcad:assert-doc expected)
  (setq doc (vla-get-ActiveDocument (vlax-get-acad-object)))
  (if path
    (pcad:require (not (findfile path)) "SAVEAS_OUTPUT_EXISTS")
    (setq path (pcad:fullpath)))
  (vla-SaveAs doc path format)
  (pcad:require (= (getvar "DBMOD") 0) "SAVE_NOT_CLEAN")
  (pcad:json (pcad:obj (list (cons "drawing" (pcad:fullpath)) (cons "bytes" (vl-file-size (pcad:fullpath))) (cons "dbmod" (getvar "DBMOD"))))))
(princ)

;;; Bounded export: top-level entities or flattened block-definition records.
(defun pcad:export-page (expected path offset limit definitions / f ss i total count e b obj record)
  (pcad:assert-doc expected)
  (pcad:require (and (>= offset 0) (> limit 0) (<= limit 500)) "EXPORT_PAGE_LIMIT_1_TO_500")
  (pcad:require (not (findfile path)) "EXPORT_OUTPUT_EXISTS")
  (setq f (open path "w" "utf8") count 0 i 0 total 0)
  (pcad:require f "OUTPUT_OPEN_FAILED")
  (write-line (pcad:json (pcad:obj (list (cons "record" "header") (cons "data" (pcad:inventory))))) f)
  (if definitions
    (vlax-for b (vla-get-Blocks (vla-get-ActiveDocument (vlax-get-acad-object)))
      (if (and (= (vla-get-IsLayout b) :vlax-false) (= (vla-get-IsXRef b) :vlax-false))
        (vlax-for obj b
          (if (and (>= i offset) (< count limit))
            (progn (setq e (vlax-vla-object->ename obj))
              (write-line (pcad:json (pcad:obj (list (cons "record" "block_entity") (cons "block" (vla-get-Name b)) (cons "data" (pcad:entity e))))) f)
              (setq count (1+ count))))
          (setq i (1+ i)))))
    (progn
      (setq ss (ssget "_X") i (if ss (sslength ss) 0))
      (while (and (< (+ offset count) i) (< count limit))
        (setq e (ssname ss (+ offset count)))
        (write-line (pcad:json (pcad:obj (list (cons "record" "entity") (cons "data" (pcad:entity e))))) f)
        (setq count (1+ count)))))
  (setq total i)
  (write-line (pcad:json (pcad:obj (list (cons "record" "complete") (cons "offset" offset)
    (cons "count" count) (cons "total" total) (cons "definitions" (if definitions T 'pcad-false))))) f)
  (close f)
  (pcad:json (pcad:obj (list (cons "path" path) (cons "count" count) (cons "total" total)
    (cons "next" (if (< (+ offset count) total) (+ offset count) nil))))))
(princ)

;;; Activate each layout to obtain valid viewport numbers (inactive tabs report 0).
(defun pcad:frames-work (expected / doc lo ss i e out)
  (pcad:assert-doc expected)
  (setq doc (vla-get-ActiveDocument (vlax-get-acad-object)) out nil)
  (vlax-for lo (vla-get-Layouts doc)
    (if (/= (vla-get-Name lo) "Model")
      (progn (vla-put-ActiveLayout doc lo)
        (setq ss (ssget "_X" (list '(0 . "VIEWPORT") (cons 410 (vla-get-Name lo)))) i 0)
        (if ss (repeat (sslength ss)
          (setq e (ssname ss i) i (1+ i))
          (if (> (cdr (assoc 69 (entget e))) 1) (setq out (cons (pcad:entity e) out))))))))
  (pcad:json (pcad:arr (reverse out))))
(defun pcad:frames (expected / tab result)
  (setq tab (getvar "CTAB"))
  (setq result (vl-catch-all-apply 'pcad:frames-work (list expected)))
  (setvar "CTAB" tab)
  (if (vl-catch-all-error-p result) (pcad:fail (pcad:message result)) result))
(princ)
